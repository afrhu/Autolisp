(defun c:plotsin()
	(command "_osnap" "off")
	(setq x 0.0 dx 0.01 xmax (* 2.0 pi 1.0) A 2.0 w 1.0)
	(while (< x xmax)
		(setq p1 (list x (* A (sin (* w x)))))
		(setq p2 (list (+ x dx) (* A (sin (* w (+ x dx))))))
		(command "_line" p1 p2 "")
		(setq x (+ x dx))
	)	
)

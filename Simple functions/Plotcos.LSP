(defun c:plotcos()
	(command "_osnap" "off")
	(setq x 0.0 dx 0.01 xmax (* 2.0 pi 1.0) A 2.0 w 1.0)
	(while (< x xmax)
		(setq p1 (list x (* A (cos (* w x)))))
		(setq p2 (list (+ x dx) (* A (cos (* w (+ x dx))))))
		(command "_line" p1 p2 "")
		(setq x (+ x dx))
	)	
)
